# -*- coding:utf-8 -*-
import FreeCAD as App, FreeCADGui as Gui, Part, math

doc_name = "CassiniUltra_HeavySatellite_RadiationShield_MULTILAYER"
doc = App.ActiveDocument if App.ActiveDocument and App.ActiveDocument.Label == doc_name else App.newDocument(doc_name)
doc = App.ActiveDocument

# -----------------------------
# Parámetros
# -----------------------------
P = {
    "shield_shape":"box",  # "cyl" o "box"
    "tank_len":11000.0, "tank_d":6000.0,
    "hull_t":85.0, "hull_outer_d":7000.0, "liner_t":36.0,
    "tps_front_R":4200.0, "tps_front_t":220.0, "tps_offset":780.0, "shoulder_len":1600.0,
    "bus_len":5200.0, "bus_outer_d":6800.0, "bus_inner_d":5600.0,
    "hga_R":2800.0, "hga_t":32.0, "hga_offset":880.0, "hga_mast_len":2000.0, "hga_mast_d":320.0,
    "rtg_box_l":1600.0, "rtg_box_w":920.0, "rtg_box_t":420.0,
    "rtg_arm_len":1650.0, "rtg_arm_d":320.0, "rtg_arm_offset_z":1400.0,
    "throat_d":900.0, "exit_d":5600.0, "nozzle_len":4600.0,
    "gimbal_ring_ro":2800.0, "gimbal_ring_t":160.0,
    "bulkhead_t":90.0, "frame_ring_d":4600.0, "frame_ring_t":140.0, "frame_step":800.0,
    "rcs_thr_d":520.0, "rcs_thr_len":900.0, "rcs_ring_R":4200.0, "rcs_count":12,
    "aux_thr_d":1200.0, "aux_thr_len":1800.0, "aux_thr_ring_R":4800.0, "aux_thr_count":12,

    # Blindaje radial (para modo cilíndrico)
    "rad_shield_inner_d":7600.0, "rad_shield_gap":120.0, "rad_shield_len":7600.0,
    "whipple_t":80.0, "whipple_gap":300.0,

    # Blindaje rectangular (dimensiones internas base del “cofre”)
    "shield_box_L":7600.0, "shield_box_W":7600.0, "shield_box_H":7600.0,

    "inst_bay_len":2400.0, "inst_bay_d":4800.0,
    "mag_boom_len":5200.0, "mag_boom_d":220.0,
    "star_boom_len":3800.0, "star_boom_d":180.0,
    "fin_len":1600.0, "fin_w":940.0, "fin_t":180.0,
    "ion_thr_d":380.0, "ion_thr_len":1100.0, "ion_ring_R":3600.0, "ion_count":16,
    "hall_thr_d":720.0, "hall_thr_len":1400.0, "hall_arm_len":1800.0,
    "rad_len":3200.0, "rad_w":1400.0, "rad_t":90.0, "rad_z":1800.0,
    "parker_shield_R":3200.0, "engine_bay_len":2800.0
}

MATS = {
    "Hull":{"name":"Ti-6Al-4V","rho":4430,"E":114e9,"nu":0.34},
    "Tank":{"name":"Al-Li 2195","rho":2700,"E":73e9,"nu":0.33},
    "Shield":{"name":"CFRP+PE+W","rho":1900,"E":60e9,"nu":0.28},
    "Whipple":{"name":"Al 6061-T6","rho":2700,"E":69e9,"nu":0.33},
    "Nozzle":{"name":"C/SiC","rho":2600,"E":300e9,"nu":0.15},
    "RTG":{"name":"Inconel+Graphite","rho":8200,"E":200e9,"nu":0.29},
    "Booms":{"name":"Al 7075-T6","rho":2810,"E":72e9,"nu":0.33},
    "Radiator":{"name":"Al+Ammonia plate","rho":1500,"E":40e9,"nu":0.29},
    "HGA":{"name":"CFRP Honeycomb","rho":1400,"E":70e9,"nu":0.30},
    "Avionics":{"name":"Al Frame + PCB","rho":2200,"E":50e9,"nu":0.30},
    "PE_Shield":{"name":"HDPE","rho":950,"E":1.1e9,"nu":0.42},
    "TrayCube":{"name":"Al 7075 + CFRP","rho":1750,"E":60e9,"nu":0.30},
    "TrayCirc":{"name":"Al 6061 + CFRP","rho":1800,"E":58e9,"nu":0.30},
    "Rail":{"name":"Ti-6Al-4V","rho":4430,"E":114e9,"nu":0.34}
}

# -----------------------------
# Utilidades geométricas
# -----------------------------
X_AXIS=App.Vector(1,0,0); Y_AXIS=App.Vector(0,1,0); Z_AXIS=App.Vector(0,0,1)
rot_to_x = lambda: App.Rotation(Y_AXIS, 90)

def add_obj(s, n):
    o = doc.addObject("Part::Feature", n)
    o.Shape = s
    return o

def color(o, rgb):
    if hasattr(o, "ViewObject"):
        o.ViewObject.ShapeColor = rgb
    return o

def cyl_x(d, L, cx=0, cy=0, cz=0):
    s = Part.makeCylinder(d/2.0, L)
    s.Placement = App.Placement(App.Vector(cx - L/2.0, cy, cz), rot_to_x())
    return s

def cone_x(d1, d2, L, cx=0, cy=0, cz=0):
    s = Part.makeCone(d1/2.0, d2/2.0, L)
    s.Placement = App.Placement(App.Vector(cx - L/2.0, cy, cz), rot_to_x())
    return s

def sphere_section(R, t, cx):
    so, si = Part.makeSphere(R), Part.makeSphere(R - t)
    so.Placement = si.Placement = App.Placement(App.Vector(cx, 0, 0), App.Rotation())
    box = Part.makeBox(2*R, 4*R, 4*R, App.Vector(cx, -2*R, -2*R))
    return so.common(box).cut(si.common(box))

def box_at(l, w, t, x, y, z):
    b = Part.makeBox(l, w, t)
    b.translate(App.Vector(x, y, z))
    return b

def box_x(l, w, h, cx=0, cy=0, cz=0):
    b = Part.makeBox(l, w, h)
    b.Placement = App.Placement(
        App.Vector(cx - l/2.0, cy - w/2.0, cz - h/2.0), App.Rotation()
    )
    return b

# -----------------------------
# Blindaje multicapa (cilíndrico y rectangular)
# -----------------------------
def multilayer_shield_cyl(cx, L, inner_d, layers):
    shapes = []
    current_d = inner_d
    for t, col, name in layers:
        outer = cyl_x(current_d + 2*t, L, cx=cx)
        inner = cyl_x(current_d, L - 2*P["rad_shield_gap"], cx=cx)
        layer = outer.cut(inner)
        shapes.append(color(add_obj(layer, name), col))
        current_d += 2*t
    return shapes, current_d

def multilayer_shield_box(cx, L, W, H, layers):
    shapes = []
    curL, curW, curH = L, W, H
    for t, col, name in layers:
        outer = box_x(curL + 2*t, curW + 2*t, curH + 2*t, cx=cx)
        inner = box_x(curL, curW, curH, cx=cx)
        layer = outer.cut(inner)
        shapes.append(color(add_obj(layer, name), col))
        curL, curW, curH = curL + 2*t, curW + 2*t, curH + 2*t
    return shapes, (curL, curW, curH)

# -----------------------------
# Construcción
# -----------------------------
tank_cx = 0.0
tank = cyl_x(P["tank_d"], P["tank_len"], cx=tank_cx)
color(add_obj(tank, "Tank"), (0.75,0.75,0.8))

layers = [
    (80.0, (0.9,0.9,0.6), "PE_Layer"),
    (60.0, (0.3,0.3,0.3), "CFRP_Layer"),
    (40.0, (0.5,0.5,0.7), "W_Layer")
]

if P["shield_shape"] == "cyl":
    shield_layers, final_d = multilayer_shield_cyl(
        tank_cx, P["rad_shield_len"], P["rad_shield_inner_d"], layers
    )
    whipple_outer = cyl_x(P["rad_shield_inner_d"] + 2*(sum([l[0] for l in layers]) + P["whipple_gap"]),
                          P["rad_shield_len"], cx=tank_cx)
    whipple_inner = cyl_x(P["rad_shield_inner_d"] + 2*(sum([l[0] for l in layers]) + P["whipple_gap"] - P["whipple_t"]),
                          P["rad_shield_len"], cx=tank_cx)
    whipple = whipple_outer.cut(whipple_inner)
    color(add_obj(whipple, "WhippleShield"), (0.8,0.8,0.8))
else:
    shield_layers, (curL, curW, curH) = multilayer_shield_box(
        tank_cx, P["shield_box_L"], P["shield_box_W"], P["shield_box_H"], layers
    )
    whL = curL + 2*(P["whipple_gap"])
    whW = curW + 2*(P["whipple_gap"])
    whH = curH + 2*(P["whipple_gap"])
    whL_in = whL - 2*P["whipple_t"]
    whW_in = whW - 2*P["whipple_t"]
    whH_in = whH - 2*P["whipple_t"]
    whipple_outer = box_x(whL, whW, whH, cx=tank_cx)
    whipple_inner = box_x(whL_in, whW_in, whH_in, cx=tank_cx)
    whipple = whipple_outer.cut(whipple_inner)
    color(add_obj(whipple, "WhippleShieldBox"), (0.8,0.8,0.8))

# -----------------------------
# Parker Solar Probe: frente térmico y hombro
# -----------------------------
cap_center_x = tank_cx + P["tank_len"]/2.0 + P["tps_offset"]
tps_front = sphere_section(P["tps_front_R"], P["tps_front_t"], cap_center_x)
color(add_obj(tps_front, "TPS_Front"), (0.85,0.85,0.9))
shoulder_cx = cap_center_x - P["shoulder_len"]/2.0
shoulder = cone_x(2*P["tps_front_R"], P["hull_outer_d"], P["shoulder_len"], cx=shoulder_cx)
color(add_obj(shoulder, "TPS_Shoulder"), (0.7,0.7,0.75))

parker = cyl_x(P["parker_shield_R"]*2.0, 240.0, cx=cap_center_x + P["tps_offset"] + 220.0)
color(add_obj(parker, "ParkerShield"), (0.8,0.8,0.9))

# -----------------------------
# Casco, liner, bus y resto
# -----------------------------
liner = cyl_x(P["tank_d"] - 2*P["liner_t"], P["tank_len"] - 2*P["liner_t"], cx=tank_cx)
color(add_obj(liner, "TankLiner"), (0.6,0.6,0.65))

hull = cyl_x(P["hull_outer_d"], P["tank_len"], cx=tank_cx).cut(tank)
color(add_obj(hull, "Hull"), (0.55,0.55,0.6))

bus_shell = cyl_x(P["bus_outer_d"], P["bus_len"], cx=tank_cx).cut(
    cyl_x(P["bus_inner_d"], P["bus_len"] - 2*P["hull_t"], cx=tank_cx)
)
color(add_obj(bus_shell, "BusShell"), (0.55,0.55,0.6))

hga_mast = cyl_x(P["hga_mast_d"], P["hga_mast_len"], cx=cap_center_x + P["hga_offset"])
color(add_obj(hga_mast, "HGAMast"), (0.6,0.6,0.65))

disk = Part.makeCylinder(P["hga_R"], P["hga_t"])
disk.Placement = App.Placement(
    App.Vector(cap_center_x + P["hga_offset"] + P["hga_mast_len"], 0, -P["hga_R"]/2.0),
    App.Rotation(Y_AXIS, 90)
)
color(add_obj(disk, "HGA"), (0.9,0.9,0.9))

rtg_center_x = tank_cx - P["tank_len"]/2.0 - P["rtg_arm_len"]/2.0
rtg_box = box_at(P["rtg_box_l"], P["rtg_box_w"], P["rtg_box_t"], rtg_center_x, 0, -P["rtg_arm_offset_z"])
rtg_arm = cyl_x(P["rtg_arm_d"], P["rtg_arm_len"], cx=rtg_center_x)
rtg_total = rtg_arm.fuse(rtg_box)
color(add_obj(rtg_total, "RTGAssembly"), (0.8,0.7,0.5))

rad1 = box_at(P["rad_len"], P["rad_w"], P["rad_t"], tank_cx + P["tank_len"]/3.0, 0, P["rad_z"])
rad2 = box_at(P["rad_len"], P["rad_w"], P["rad_t"], tank_cx + P["tank_len"]/3.0, 0, -P["rad_z"])
color(add_obj(rad1.fuse(rad2), "Radiators"), (0.8,0.9,1.0))

boom_mag = cyl_x(P["mag_boom_d"], P["mag_boom_len"], cx=tank_cx + P["tank_len"]/2.0 + P["mag_boom_len"]/2.0)
color(add_obj(boom_mag, "MagBoom"), (0.7,0.7,0.7))

boom_star = cyl_x(P["star_boom_d"], P["star_boom_len"], cx=tank_cx - P["tank_len"]/2.0 - P["star_boom_len"]/2.0)
color(add_obj(boom_star, "StarBoom"), (0.7,0.7,0.7))

nozzle_axis_cx = tank_cx - P["tank_len"]/2.0 - P["nozzle_len"]/2.0
nozzle = cyl_x(P["exit_d"], P["nozzle_len"], cx=nozzle_axis_cx).cut(
    cone_x(P["exit_d"], P["throat_d"], P["nozzle_len"], cx=nozzle_axis_cx)
)
color(add_obj(nozzle, "Nozzle"), (0.4,0.4,0.45))

gimbal_cx = tank_cx - P["tank_len"]/2.0 - P["nozzle_len"] - P["gimbal_ring_t"]/2.0
gimbal_ring = cyl_x(P["gimbal_ring_ro"], P["gimbal_ring_t"], cx=gimbal_cx).cut(
    cyl_x(P["gimbal_ring_ro"] - P["gimbal_ring_t"], P["gimbal_ring_t"], cx=gimbal_cx)
)
color(add_obj(gimbal_ring, "GimbalRing"), (0.6,0.6,0.65))

# -----------------------------
# Final
# -----------------------------
App.ActiveDocument.recompute()
Gui.SendMsgToActiveView("ViewFit")
