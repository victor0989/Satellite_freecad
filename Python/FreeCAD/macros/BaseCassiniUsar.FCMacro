# -*- coding:utf-8 -*-
import FreeCAD as App, FreeCADGui as Gui, Part, math

doc_name = "CassiniUltra_HeavySatellite_RadiationShield_SOLID_INTEGRATED_ELEC"
doc = App.ActiveDocument if App.ActiveDocument and App.ActiveDocument.Label == doc_name else App.newDocument(doc_name)
doc = App.ActiveDocument

# ========================= Parameters =========================
P = {
    "tank_len": 11000.0, "tank_d": 6000.0,
    "hull_t": 85.0, "hull_outer_d": 7000.0, "liner_t": 36.0,
    "tps_front_R": 4200.0, "tps_front_t": 220.0, "tps_offset": 780.0, "shoulder_len": 1600.0,
    "bus_len": 5200.0, "bus_outer_d": 6800.0, "bus_inner_d": 5600.0,
    "hga_R": 2800.0, "hga_t": 32.0, "hga_offset": 880.0, "hga_mast_len": 2000.0, "hga_mast_d": 320.0,
    "rtg_box_l": 1600.0, "rtg_box_w": 920.0, "rtg_box_t": 420.0, "rtg_arm_len": 1650.0, "rtg_arm_d": 320.0, "rtg_arm_offset_z": 1400.0,
    "throat_d": 900.0, "exit_d": 5600.0, "nozzle_len": 4600.0,
    "gimbal_ring_ro": 2800.0, "gimbal_ring_t": 160.0,
    "bulkhead_t": 90.0, "frame_ring_d": 4600.0, "frame_ring_t": 140.0, "frame_step": 800.0,
    "rcs_thr_d": 520.0, "rcs_thr_len": 900.0, "rcs_ring_R": 4200.0, "rcs_count": 12,
    "aux_thr_d": 1200.0, "aux_thr_len": 1800.0, "aux_thr_ring_R": 4800.0, "aux_thr_count": 12,
    "rad_shield_inner_d": 7600.0, "rad_shield_t": 220.0, "rad_shield_gap": 120.0, "rad_shield_len": 7600.0,
    "whipple_t": 80.0, "whipple_gap": 300.0,
    "inst_bay_len": 2400.0, "inst_bay_d": 4800.0,
    "mag_boom_len": 5200.0, "mag_boom_d": 220.0, "star_boom_len": 3800.0, "star_boom_d": 180.0,
    "fin_len": 1600.0, "fin_w": 940.0, "fin_t": 180.0,
    "ion_thr_d": 380.0, "ion_thr_len": 1100.0, "ion_ring_R": 3600.0, "ion_count": 16,
    "hall_thr_d": 720.0, "hall_thr_len": 1400.0, "hall_arm_len": 1800.0,
    "rad_len": 3200.0, "rad_w": 1400.0, "rad_t": 90.0, "rad_z": 1800.0,
    "parker_shield_R": 3200.0, "engine_bay_len": 2800.0,
    # Avionics
    "avionics_bay_len": 3800.0, "avionics_bay_d": 5400.0, "avionics_clear_h": 2600.0,
    "rack_w": 620.0, "rack_t": 40.0, "rack_h": 2200.0, "rack_count": 8, "shelf_count": 9,
    "aisle_w": 900.0, "rail_w": 60.0, "rail_t": 22.0,
    "bay_len": 700.0, "bay_w": 820.0, "bay_h": 420.0, "bay_rows": 3, "bay_cols": 4, "bay_gap": 180.0,
    "faraday_t": 8.0,
    "inner_shield_len": 4200.0, "cc_t": 12.0, "kevlar_t": 10.0, "epoxy_t": 6.0, "shield_gap": 60.0,
}

# ========================= Materials =========================
MATS = {
    "Hull": {"rho": 4430}, "Tank": {"rho": 2700}, "Shield": {"rho": 1900},
    "Whipple": {"rho": 2700}, "Nozzle": {"rho": 2600}, "RTG": {"rho": 8200},
    "Booms": {"rho": 2810}, "Radiator": {"rho": 1500}, "HGA": {"rho": 1400},
    "Avionics": {"rho": 2200}, "Rail": {"rho": 4430},
    "FaradayCap": {"rho": 2700}, "CarbonCarbon": {"rho": 1700},
    "Kevlar": {"rho": 1400}, "EpoxyResin": {"rho": 1200},
}

# ========================= Helpers =========================
X_AXIS = App.Vector(1,0,0); Y_AXIS = App.Vector(0,1,0); Z_AXIS = App.Vector(0,0,1)
rot_to_x = lambda: App.Rotation(Y_AXIS,90)

def add_obj(s,n): o=doc.addObject("Part::Feature",n); o.Shape=s; return o
def color(o,rgb): 
    if hasattr(o,"ViewObject"): o.ViewObject.ShapeColor=rgb
def cyl_x(d,L,cx=0,cy=0,cz=0):
    s=Part.makeCylinder(d/2.0,L); s.Placement=App.Placement(App.Vector(cx-L/2.0,cy,cz),rot_to_x()); return s
def cone_x(d1,d2,L,cx=0,cy=0,cz=0):
    s=Part.makeCone(d1/2.0,d2/2.0,L); s.Placement=App.Placement(App.Vector(cx-L/2.0,cy,cz),rot_to_x()); return s
def sphere_section(R,t,cx):
    so,si=Part.makeSphere(R),Part.makeSphere(R-t)
    so.Placement=si.Placement=App.Placement(App.Vector(cx,0,0),App.Rotation())
    box=Part.makeBox(2*R,4*R,4*R,App.Vector(cx,-2*R,-2*R))
    return so.common(box).cut(si.common(box))
def box_at(l,w,t,x,y,z): b=Part.makeBox(l,w,t); b.translate(App.Vector(x,y,z)); return b
def refine_shape(shp): 
    try: return shp.removeSplitter()
    except Exception: return shp

# ========================= Base geometry =========================
tank_cx=0.0
tank=cyl_x(P["tank_d"],P["tank_len"],cx=tank_cx)
liner=cyl_x(P["tank_d"]-2*P["liner_t"],P["tank_len"]-2*P["liner_t"],cx=tank_cx)
hull=cyl_x(P["hull_outer_d"],P["tank_len"],cx=tank_cx).cut(tank)

bus_shell=cyl_x(P["bus_outer_d"],P["bus_len"],cx=tank_cx).cut(cyl_x(P["bus_inner_d"],P["bus_len"]-2*P["hull_t"],cx=tank_cx))
cap_center_x=tank_cx+P["tank_len"]/2.0+P["tps_offset"]
tps_front=sphere_section(P["tps_front_R"],P["tps_front_t"],cap_center_x)
shoulder_cx=cap_center_x-P["shoulder_len"]/2.0
shoulder=cone_x(2*P["tps_front_R"],P["hull_outer_d"],P["shoulder_len"],cx=shoulder_cx)

# ========================= Avionics bay (simplificado) =========================
payload_cx=tank_cx+P["tank_len"]/2.0-P["bus_len"]/2.0
bus_center_x=payload_cx
avionics_shell= cyl_x(P["avionics_bay_d"],P["avionics_bay_len"],cx=bus_center_x)

# Racks
rack_y_positions=[-1000,1000]
racks=[]
for ry in rack_y_positions:
    # dos raíles verticales
    rail_L = box_at(P["rack_h"], P["rail_w"], P["rail_t"],
                    bus_center_x - P["rack_h"]/2.0, ry - P["rack_w"]/2.0 - 36.0, -P["avionics_clear_h"]/2.0)
    rail_R = box_at(P["rack_h"], P["rail_w"], P["rail_t"],
                    bus_center_x - P["rack_h"]/2.0, ry + P["rack_w"]/2.0 + 36.0, -P["avionics_clear_h"]/2.0)
    rack = rail_L.fuse(rail_R)
    # bandejas
    for s in range(P["shelf_count"]):
        z_shelf = -P["avionics_clear_h"]/2.0 + 120.0 + s*((P["avionics_clear_h"]-240.0)/max(P["shelf_count"]-1,1))
        shelf = box_at(P["avionics_bay_len"]-200.0, P["rack_w"], P["rack_t"],
                       bus_center_x - (P["avionics_bay_len"]-200.0)/2.0, ry - P["rack_w"]/2.0, z_shelf)
        rack = rack.fuse(shelf)
    racks.append(rack)

# Fusionar racks en un solo sólido
racks_shp = racks[0]
for r in racks[1:]:
    racks_shp = racks_shp.fuse(r)

# ========================= Bays electrónicos =========================
bay_objs=[]
bay_index=1
for r in range(P["bay_rows"]):
    for c in range(P["bay_cols"]):
        if bay_index>12: break
        x = bus_center_x - P["bay_len"]/2.0 + c*(P["bay_len"]+P["bay_gap"])
        y = -((P["bay_cols"]-1)/2.0)*(P["bay_w"]+P["bay_gap"]) + c*(P["bay_w"]+P["bay_gap"])
        z = -((P["bay_rows"]-1)/2.0)*(P["bay_h"]+P["bay_gap"]) + r*(P["bay_h"]+P["bay_gap"])
        bay_box = box_at(P["bay_len"],P["bay_w"],P["bay_h"],x,y,z)
        add_obj(bay_box,f"Bay{bay_index:02d}")
        color(doc.getObject(f"Bay{bay_index:02d}"),(0.25+0.02*bay_index,0.35,0.55))
        bay_objs.append(bay_box)
        bay_index+=1

# Fusionar bays
bays_shp = bay_objs[0]
for b in bay_objs[1:]:
    bays_shp = bays_shp.fuse(b)

# ========================= Penthouse =========================
penthouse = box_at(P["bay_len"]*1.1, P["avionics_bay_d"]-P["aisle_w"]-320.0, 260.0,
                   bus_center_x,0,P["avionics_clear_h"]/2.0+200.0)
add_obj(penthouse,"PenthouseRadar")
color(doc.getObject("PenthouseRadar"),(0.30,0.50,0.65))

# ========================= Faraday cage =========================
faraday_cap = Part.makeCylinder(P["bus_outer_d"]/2.0, P["faraday_t"])
faraday_cap.Placement = App.Placement(App.Vector(bus_center_x,0,P["avionics_clear_h"]/2.0+260.0),App.Rotation(Y_AXIS,90))
add_obj(faraday_cap,"FaradayCap")
color(doc.getObject("FaradayCap"),(0.85,0.85,0.90))

# ========================= Blindajes internos =========================
shield_cx=tank_cx
shield_len=P["inner_shield_len"]
base_d=P["rad_shield_inner_d"]-2*P["shield_gap"]

cc_layer=cyl_x(base_d,shield_len,cx=shield_cx).cut(cyl_x(base_d-2*P["cc_t"],shield_len-2*P["shield_gap"],cx=shield_cx))
kev_layer=cyl_x(base_d-2*P["cc_t"]-2*P["shield_gap"],shield_len,cx=shield_cx).cut(
          cyl_x(base_d-2*P["cc_t"]-2*P["shield_gap"]-2*P["kevlar_t"],shield_len-2*P["shield_gap"],cx=shield_cx))
ep_layer=cyl_x(base_d-2*(P["cc_t"]+P["kevlar_t"])-4*P["shield_gap"],shield_len,cx=shield_cx).cut(
         cyl_x(base_d-2*(P["cc_t"]+P["kevlar_t"]+P["epoxy_t"])-4*P["shield_gap"],shield_len-2*P["shield_gap"],cx=shield_cx))

add_obj(cc_layer,"InnerShield_CarbonCarbon"); color(doc.getObject("InnerShield_CarbonCarbon"),(0.15,0.15,0.18))
add_obj(kev_layer,"InnerShield_Kevlar");      color(doc.getObject("InnerShield_Kevlar"),(0.90,0.90,0.40))
add_obj(ep_layer,"InnerShield_Epoxy");        color(doc.getObject("InnerShield_Epoxy"),(0.70,0.75,0.80))

# ========================= Fusionar avionics =========================
avionics_total = avionics_shell.fuse(racks_shp).fuse(bays_shp).fuse(penthouse)
add_obj(refine_shape(avionics_total),"AvionicsBayTotal")
color(doc.getObject("AvionicsBayTotal"),(0.22,0.38,0.58))

# ========================= Integrar al core =========================
core = tank.fuse(liner).fuse(hull).fuse(bus_shell).fuse(tps_front).fuse(shoulder)
core = core.fuse(avionics_total).fuse(cc_layer).fuse(kev_layer).fuse(ep_layer).fuse(faraday_cap)
core = refine_shape(core)
add_obj(core,"CassiniUltra_HeavySatellite")
color(doc.getObject("CassiniUltra_HeavySatellite"),(0.55,0.55,0.60))

App.ActiveDocument.recompute()
Gui.SendMsgToActiveView("ViewFit")
print("Modelo Cassini Ultra Heavy con racks, bays, penthouse, Faraday cage y blindajes generado.")
